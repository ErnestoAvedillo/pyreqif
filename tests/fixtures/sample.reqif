# Sample

## _chapter-1: Introduccion

## _req-1
El sistema debe arrancar en menos de 2 segundos.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

## _req-2
El sistema debe soportar 100 usuarios concurrentes.
- Kommentar Lieferant M: Ya validado en pruebas de carga.
- Status Lieferant M: akzeptiert
